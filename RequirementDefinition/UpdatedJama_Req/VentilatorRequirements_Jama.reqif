# Functional Requirements

# Specification: VentilatorRequirements

## R1: General Requirements
- documentKey: RL1

### R2: Safety
| Ventilators must be designed to protect patients from electric shock, mechanical hazards, and excessive outputs of pressure (35 cmH2O) and volume |
| --- |
- documentKey: RL1.1

### R3: Environmental conditions
| The ventilator should function safely within a specified range of environmental conditions, including temperature and humidity |
| --- |
- documentKey: RL1.2

## R4: Mode & Operation
- documentKey: RL2.1

### R5: Operating mode
| The ventilator shall allow changing the ventilation mode while ventilation support is inactive or active |
| --- |
- documentKey: RL2.1.1

### R6: Start/Stop
| The ventilator shall provide switch input to allow start/stop ventilation operation |
| --- |
- documentKey: RL2.1.2

### R7: Monitoring
| The ventilator shall provide monitoring switch to allow display all essential patient vitals such as tidal volume, pressure, flow, inhale/exhale time |
| --- |
- documentKey: RL2.1.3

### R8: Press control
| The pressure controller ventilator shall be operate within a range of 5 to 50 cm H2O |
| --- |
- documentKey: RL2.1.4

### R9: PEEP adjustment
| The ventilation modes that utilizes PEEP adjustment shall range between 5 to 10 cmH2O |
| --- |
- documentKey: RL2.1.5

### R10: Breath rate
| The ventilation modes that utilizes breath rate shall range between 1 to 60 breath/min |
| --- |
- documentKey: RL2.1.6

### R11: Insp time
| The Inspirational time adjustment range shall be 0.3s to 2.4s with an I/E ratio not exceeding 1/2 for pressure controlled ventilator |
| --- |
- documentKey: RL2.1.7

### R12: Pressure level
| The rise time adjustment range shall allow 6 levels. The associated quantitative rise times will adapt to inspiration time and the adjusted inspiratory pressure value |
| --- |
- documentKey: RL2.1.8

### R13: Heater wire humidifier
| The temperature along the inspiratory limb shall be monitored and controlled at 34degC in the non-invasive mode and 40degC in the invasive mode |
| --- |
- documentKey: RL2.1.9

### R14: Humidity requirement
| The ventilator shall deliver gas with 50% relative humidity with absolute humidity of 10mg/L at 22degC at nose/mouth |
| --- |
- documentKey: RL2.1.10

## R15: Display
- documentKey: RL2.2

### R16: Patient monitoring
| The ventilator should provide monitoring capabilities for patient parameters such as pressure, volume, and gas concentration |
| --- |
- documentKey: RL2.2.1

## R17: Alarms
- documentKey: RL2.3

### R18: Operating mode short circuit
| Operating mode dial switch logic shall able to detect shorted high or ground faults |
| --- |
- documentKey: RL2.3.1

### R19: Pressure fault
| Pressure sensor reading shall not fall below 5 or rise above 50 cmH2O while ventilation support is active |
| --- |
- documentKey: RL2.3.2

### R20: Occlusion
| The ventilator shall initiate a high priority alarm if no significant volume can be delivered to the patient while the target pressure is reached |
| --- |
- documentKey: RL2.3.3

### R21: Alarm failure
| The ventilator shall initiate a high priority alarm if the primary audio/visual alarm system is not delivering alarm signal |
| --- |
- documentKey: RL2.3.4

## R22: Controls
- documentKey: RL2.4

### R23: PID rise time
PID shall be tuned to have controller rise time < 10sec
- documentKey: RL2.4.1

## R24: Test Requirement
This is a software module test requirement
- documentKey: RL3.1
