# StakeholderRequirement_Func

## #1: Operating Environment (Container)

### STAKEHOLDER -02: Environment (Functional)
The ventilator shall be designed for indoor use.

### STAKEHOLDER -03: Operating Temperature (Functional)
The ventilator should operate within an ambient temperature range of 15°C - 32°C.

### STAKEHOLDER -04: Operating Pressure (Functional)
The ventilator shall operate at standard ambient pressure.

## #2: Performance (Functional)

### STAKEHOLDER -05: Operating Time (Functional)
The ventilator shall be able to operate continuously for 120 minutes if it is in battery mode.

### STAKEHOLDER -06: Manual Control (Functional)

## #3: System Size (Functional)

## #4: System Cost (Functional)
The cost of the ventilator shall not exceed $10000.

## #5: Mass (Functional)
The mass of the ventilator shall not exceed 15 kg.

## #6: Safety (Functional)

## #7: Reliability (Functional)

## #13: Patient Breathing (Container)

### STAKEHOLDER - 07: Humidification (Functional)
Inhale gas shall be humidified by using either an active or passive device
