# VentilatorRequirements_Jama

## VentilatorRequirements (Container)
- srcFileChecksum: F39D74E6F003B6E3585F28E501194954

### RL1: General Requirements (Container)

#### RL1.1: Safety (Functional)
| Ventilators must be designed to protect patients from electric shock, mechanical hazards, and excessive outputs of pressure (35 cmH2O) and volume |
| --- |

#### RL1.2: Environmental conditions (Functional)
| The ventilator should function safely within a specified range of environmental conditions, including temperature and humidity |
| --- |

### RL2.1: Mode & Operation (Container)

#### RL2.1.1: Operating mode (Functional)
| The ventilator shall allow changing the ventilation mode while ventilation support is inactive or active |
| --- |

#### RL2.1.2: Start/Stop (Functional)
| The ventilator shall provide switch input to allow start/stop ventilation operation |
| --- |

#### RL2.1.3: Monitoring (Functional)
| The ventilator shall provide monitoring switch to allow display all essential patient vitals such as tidal volume, pressure, flow, inhale/exhale time |
| --- |

#### RL2.1.4: Press control (Functional)
| The pressure controller ventilator shall be operate within a range of 5 to 50 cm H2O |
| --- |

#### RL2.1.5: PEEP adjustment (Functional)
| The ventilation modes that utilizes PEEP adjustment shall range between 5 to 10 cmH2O |
| --- |

#### RL2.1.6: Breath rate (Functional)
| The ventilation modes that utilizes breath rate shall range between 1 to 60 breath/min |
| --- |

#### RL2.1.7: Insp time (Functional)
| The Inspirational time adjustment range shall be 0.3s to 2.4s with an I/E ratio not exceeding 1/2 for pressure controlled ventilator |
| --- |

#### RL2.1.8: Pressure level (Functional)
| The rise time adjustment range shall allow 6 levels. The associated quantitative rise times will adapt to inspiration time and the adjusted inspiratory pressure value |
| --- |

#### RL2.1.9: Heater wire humidifier (Functional)
| The temperature along the inspiratory limb shall be monitored and controlled at 34degC in the non-invasive mode and 40degC in the invasive mode |
| --- |

#### RL2.1.10: Humidity requirement (Functional)
| The ventilator shall deliver gas with 50% relative humidity with absolute humidity of 10mg/L at 22degC at nose/mouth |
| --- |

### RL2.2: Display (Container)

#### RL2.2.1: Patient monitoring (Functional)
| The ventilator should provide monitoring capabilities for patient parameters such as pressure, volume, and gas concentration |
| --- |

### RL2.3: Alarms (Container)

#### RL2.3.1: Operating mode short circuit (Functional)
| Operating mode dial switch logic shall able to detect shorted high or ground faults |
| --- |

#### RL2.3.2: Pressure fault (Functional)
| Pressure sensor reading shall not fall below 5 or rise above 50 cmH2O while ventilation support is active |
| --- |

#### RL2.3.3: Occlusion (Functional)
| The ventilator shall initiate a high priority alarm if no significant volume can be delivered to the patient while the target pressure is reached |
| --- |

#### RL2.3.4: Alarm failure (Functional)
| The ventilator shall initiate a high priority alarm if the primary audio/visual alarm system is not delivering alarm signal |
| --- |

### RL2.4: Controls (Container)

#### RL2.4.1: PID rise time (Functional)
PID shall be tuned to have controller rise time < 10sec
